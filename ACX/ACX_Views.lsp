; =========================================================================================== ;
; Kolekcja Views / Views collection                                                           ;
; =========================================================================================== ;
(defun cd:ACX_Views ()
  (or
    *cd-Views*
    (setq *cd-Views* (vla-get-views (cd:ACX_ADoc)))
  )
  *cd-Views*
)
